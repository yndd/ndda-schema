module ndda-if-subinterface {
  yang-version 1.1;
  namespace "urn:ndda/interface/subinterface";
  prefix ndda-if-si;

	// import
	import ndda-common {
    prefix ndda-common;
  }

  // contact
  import ndda-if-si-addressinfo {
    prefix ndda-if-si-ai;
  }

  organization "NDD";

  contact
    "NDD Support Web: <http://www.yndd.com>";

	// description
  description
    "Model that describes a subinterface";

  revision 2022-01-01 {
    description
      "ndda 0.1.1";
    reference "<http://www.yndd.com>";
  }

  grouping subinterface-top {
		description
		  "Top-level grouping subinterface";

    list subinterface {
      key "index";
			max-elements 4095;
      description
        "The list of subinterfaces (logical interfaces) associated with a physical interface";

      leaf index {
        type leafref {
          path "../config/index";
        }
        description
          "The index of the subinterface, or logical interface number";
      }

      container config {
        description
          "Configuration data ";

        uses subinterface-config;
      }

      container state {
        config false;

        description
          "Operational state data ";

        uses subinterface-config;
        uses subinterface-state;
      }
      uses ndda-if-si-ai:ipv4-top;
      uses ndda-if-si-ai:ipv6-top;
		  
    }
	}

	grouping subinterface-config {
		description
		  "Grouping for subinterface config";
		
    leaf index {
      type uint32 {
        range "0..9999";
      }
      description
        "The index of the subinterface, or logical interface number";
    }

    leaf kind {
      type ndda-common:subinterface-kind;
      description
        "The kind of the subinterface";
    }

    leaf outer-vlan-id {
      type ndda-common:vlan-id;
      description
        "The outer-vlan-id";
    }

    leaf inner-vlan-id {
      type ndda-common:vlan-id;
      description
        "The inner-vlan-id";
    }
	}

	grouping subinterface-state {
		description
		  "Grouping for subinterface state";
		
		leaf status {
			type ndda-common:oper-state;
			description
				"The status of the ip resource";
		}

		leaf reason {
			type string;
			description
				"The reason why a resource is in a certain status";
		}

		container statistics {
			description
		  	"Top-level container subinterface statistics";

			uses subinterface-statistics;
		}
	}

	grouping subinterface-statistics {
		description
		  "Grouping for subinterface statistics";
		
	}
}
