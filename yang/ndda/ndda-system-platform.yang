module ndda-system-platform {
  yang-version 1.1;
  namespace "urn:ndda/system/platform";
  prefix ndda-sys-platf;

	// import
	import ndda-common {
    prefix ndda-common;
  }

	// contact
	organization "NDD";

  contact
    "NDD Support Web: <http://www.yndd.com>";

	// description
  description
    "Model that describes the system platform";

  revision 2022-01-01 {
    description
      "ndda 0.1.1";
		reference "<http://www.yndd.com>";
  }
	grouping platform-top {
		description
		  "Top-level grouping platform";

		container platform {
			description
		  	"Top-level container platform";

			container config {
      	description
        	"Configuration data ";

      	uses platform-config;
    	}

    	container state {
				config false;

      	description
        	"Operational state data ";

      	uses platform-config;
      	uses platform-state;
    	}
		}
	}

	grouping platform-config {
		description
		  "Grouping for platform config";
		
		leaf name {
			type ndda-common:name;
			description
				"The name of the device";
		}

		leaf index {
			type ndda-common:index;
			description
				"The index of the device";
		}

		leaf kind {
			type ndda-common:device-kind;
			description
				"The kind of the device";
		}

		leaf version {
			type string;
			description
				"The sw version of the device";
		}
	}

	grouping platform-state {
		description
		  "Grouping for platform state";
		
		leaf status {
			type ndda-common:oper-state;
			description
				"The status of the ip resource";
		}

		leaf reason {
			type string;
			description
				"The reason why a resource is in a certain status";
		}

		container statistics {
			description
		  	"Top-level container platform statistics";

			uses platform-statistics;
		}
	}

	grouping platform-statistics {
		description
		  "Grouping for platform statistics";
		
	}
}
