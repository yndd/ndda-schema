module ndda-common {
  yang-version 1.1;
  namespace "urn:ndda/common";
  prefix ndda-common;

  // import

	organization "NDD";

	// contact
  contact
    "NDD Support Web: <http://www.yndd.com>";

  // description
 description
    "Module defines the common types within ndda";

  revision 2022-01-01 {
    description
      "ndda 0.1.1";
		reference "<http://www.yndd.com>";
  }

  typedef alphanumeric {
    type string {
      // Add all accepted characters here
      pattern "[A-Za-z0-9 !@#$%^&()|+=`~.,'/_:;?-]*";
    }
    description
      "A simple, one-line string that does not contain any control characters";
  }

  typedef name {
    type alphanumeric {
      length "1..255";
    }
    description
      "A user provided name string";
  }

  typedef description {
    type alphanumeric {
      length "1..255";
    }
    description
      "A user provided description string";
  }

  typedef admin-state {
    type enumeration {
      enum "ENABLE" {
        description "admin state enabled";
      }
      enum "DISABLE" {
        description "admin state disabled";
      }
    }
		description
      "A user provided admin-state";
  }

  typedef oper-state {
    type enumeration {
      enum "UP" {
        description "up state";
      }
      enum "DOWN" {
        description "down state";
      }
    }
		description
      "The operational state of an object";
  }

  typedef index {
    type uint32 {
        range "1..4294967295";
    }
		description
			"An index of an object";
  }

  typedef device-kind {
    type enumeration {
      enum "SRL" {
        description "srlinux device";
      }
      enum "SROS" {
        description "sros device";
      }
    }
		description
			"Defines the kind of devices";
  }

	typedef interface-kind {
    type enumeration {
      enum "INTERFACE" {
        description "interface kind";
      }
      enum "LOOPBACK" {
        description "loopback kind";
      }
			enum "IRB" {
        description "irb kind";
      }
			enum "VXLAN" {
        description "vxlan kind";
      }
			enum "MPLS" {
        description "srv6 kind";
      }
    }
		description
			"Defines the kind of interfaces";
  }

	typedef subinterface-kind {
    type enumeration {
      enum "ROUTED" {
        description "routed kind";
      }
      enum "BRIDGED" {
        description "bridged kind";
      }
    }
		description
			"Defines the kind of subinterfaces";
  }

	typedef ni-kind {
    type enumeration {
      enum "ROUTED" {
        description "routed kind";
      }
      enum "BRIDGED" {
        description "bridge kind";
      }
    }
		description
			"Defines the kind of network instances";
  }

	typedef vlan-id {
    type uint16 {
      range 1..4094;
    }
    description
      "Type definition representing a single-tagged VLAN";
  }

	typedef counter64 {
    type uint64;
    description
     "The counter64 type represents a non-negative integer
      that monotonically increases until it reaches a
      maximum value of 2^64-1 (18446744073709551615 decimal),
      when it wraps around and starts increasing again from zero.

      Counters have no defined 'initial' value, and thus, a
      single value of a counter has (in general) no information
      content.  Discontinuities in the monotonically increasing
      value normally occur at re-initialization of the
      management system, and at other times as specified in the
      description of a schema node using this type.  If such
      other times can occur, for example, the creation of
      a schema node of type counter64 at times other than
      re-initialization, then a corresponding schema node
      should be defined, with an appropriate type, to indicate
      the last discontinuity.

      The counter64 type should not be used for configuration
      schema nodes.  A default statement SHOULD NOT be used in
      combination with the type counter64.

      In the value set and its semantics, this type is equivalent
      to the Counter64 type of the SMIv2.";
    reference
     "RFC 2578: Structure of Management Information Version 2
                (SMIv2)";
  }

  typedef zero-based-counter64 {
    type counter64;
    default "0";
    description
     "The zero-based-counter64 type represents a counter64 that
      has the defined 'initial' value zero.

      A schema node of this type will be set to zero (0) on creation
      and will thereafter increase monotonically until it reaches
      a maximum value of 2^64-1 (18446744073709551615 decimal),
      when it wraps around and starts increasing again from zero.

      Provided that an application discovers a new schema node
      of this type within the minimum time to wrap, it can use the
      'initial' value as a delta.  It is important for a management
      station to be aware of this minimum time and the actual time
      between polls, and to discard data if the actual time is too
      long or there is no defined minimum time.

      In the value set and its semantics, this type is equivalent
      to the ZeroBasedCounter64 textual convention of the SMIv2.";
    reference
     "RFC 2856: Textual Conventions for Additional High Capacity
                Data Types";
  }

	typedef ipv4-address {
    type string {
      pattern '(([0-9]|[1-9][0-9]|1[0-9][0-9]|2[0-4][0-9]|'        +
              '25[0-5])\.){3}([0-9]|[1-9][0-9]|1[0-9][0-9]|2[0-4]'  +
              '[0-9]|25[0-5])';
    }
    description
      "An IPv4 address in dotted quad notation.";
  }

  typedef ipv6-address {
    type string {
        // Must support compression through different lengths
        // therefore this regexp is complex.
        pattern
             '((:|[0-9a-fA-F]{0,4}):)([0-9a-fA-F]{0,4}:){0,5}'
             +  '((([0-9a-fA-F]{0,4}:)?(:|[0-9a-fA-F]{0,4}))|'
             +  '(((25[0-5]|2[0-4][0-9]|[01]?[0-9]?[0-9])\.){3}'
             +  '(25[0-5]|2[0-4][0-9]|[01]?[0-9]?[0-9])))';
    }
    description
      "An IPv6 address represented as either a full address; shortened
      or mixed-shortened formats.";
  }

  typedef ipv4-prefix {
    // db-class IpPrefix
    type string {
      pattern '(([0-9]|[1-9][0-9]|1[0-9][0-9]|2[0-4][0-9]|'       +
              '25[0-5])\.){3}([0-9]|[1-9][0-9]|1[0-9][0-9]|2[0-4]' +
              '[0-9]|25[0-5])/(([0-9])|([1-2][0-9])|(3[0-2]))';
    }
    description
      "An IPv4 prefix represented in dotted quad notation followed by
      a slash and a CIDR mask (0 <= mask <= 32).";
  }

  typedef ipv6-prefix {
    // db-class IpPrefix
    type string {
        pattern
             '((:|[0-9a-fA-F]{0,4}):)([0-9a-fA-F]{0,4}:){0,5}'
             +  '((([0-9a-fA-F]{0,4}:)?(:|[0-9a-fA-F]{0,4}))|'
             +  '(((25[0-5]|2[0-4][0-9]|[01]?[0-9]?[0-9])\.){3}'
             +  '(25[0-5]|2[0-4][0-9]|[01]?[0-9]?[0-9])))'
             +  '(/(([0-9])|([0-9]{2})|(1[0-1][0-9])|(12[0-8])))';
    }
    description
      "An IPv6 prefix represented in full, shortened, or mixed
      shortened format followed by a slash and CIDR mask (0 <= mask <=
      128).";
  }

  typedef ip-address {
    // db-class IpAddress
    type union {
      type ipv4-address;
      type ipv6-address;
    }
    description
      "An IPv4 or IPv6 address with no prefix specified.";
  }

  typedef ip-prefix {
    // db-class IpPrefix
    type union {
      type ipv4-prefix;
      type ipv6-prefix;
    }
    description
      "An IPv4 or IPv6 prefix.";
  }

  typedef ipv4-prefix-with-host-bits {
    type ipv4-prefix;
    description
      "An IPv4 prefix with host bits.";
  }

  typedef ipv6-prefix-with-host-bits {
    type ipv6-prefix;
    description
      "An IPv6 prefix with host bits.";
  }

  typedef ip-prefix-with-host-bits {
    type ip-prefix;
    description
      "An IPv4 or IPv6 prefix with host bits.";
  }
}
